package Interfaces {
  doc
  /* HINWEIS: Fuer diese Datei druckt das Lehrbuch keinen Code-Block ab.
     Abschnitt 4.11 "Empfohlene Modellstruktur" nennt nur den Zweck:

       "05_interfaces.sysml: Ports, Verbindungen und Datenflüsse"

     Kapitel 9 (Verbindungsmodellierung mit port und connection)
     zeigt dazu nur eigenstaendige, generische Lehrbeispiele
     (port def ImagePort, ScanPort, ObjectListPort etc.), die im
     Text nicht explizit dieser Projektdatei zugeordnet werden.
     Es gibt keine abgedruckte Musterloesung fuer 05_interfaces.sysml.
     Dieser Platzhalter enthaelt daher absichtlich keinen erfundenen
     SysML-Code. */
}
