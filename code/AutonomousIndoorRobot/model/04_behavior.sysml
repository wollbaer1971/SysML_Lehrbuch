package Behavior {
  doc
  /* HINWEIS: Fuer diese Datei druckt das Lehrbuch keinen Code-Block ab.
     Abschnitt 4.11 "Empfohlene Modellstruktur" nennt nur den Zweck:

       "04_behavior.sysml: Aktionen, Abläufe und Zustände"

     Kapitel 12 (state def, Zustandsmaschinen) und Kapitel 13
     (calc def / constraint def) zeigen dazu nur eigenstaendige,
     generische Lehrbeispiele (z. B. state def RobotOperation,
     calc def OperatingTimeCalc, constraint def SafeBrakingDistance),
     die im Text nicht explizit dieser Projektdatei zugeordnet werden.
     Es gibt keine abgedruckte Musterloesung fuer 04_behavior.sysml.
     Dieser Platzhalter enthaelt daher absichtlich keinen erfundenen
     SysML-Code. */
}
