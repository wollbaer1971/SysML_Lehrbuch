package Context {
  doc
  /* HINWEIS: Fuer diese Datei druckt das Lehrbuch keinen Code-Block ab.
     Abschnitt 4.11 "Empfohlene Modellstruktur" nennt nur den Zweck:

       "01_context.sysml: Stakeholder, externe Systeme und Umgebung"

     Die Ausarbeitung bleibt im Buch bewusst dem Leser als Uebung
     ueberlassen (siehe Kapitel 4 "Uebungen"). Es gibt keine im Text
     abgedruckte Musterloesung, die hier wortwoertlich uebernommen
     werden koennte. Dieser Platzhalter enthaelt daher absichtlich
     keinen erfundenen SysML-Code. */
}
